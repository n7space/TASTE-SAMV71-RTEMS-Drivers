SAMV71-RTEMS-SERIAL-DRIVER DEFINITIONS AUTOMATIC TAGS ::= BEGIN

Serial-SamV71-Rtems-Device-T    ::= CHOICE {
   uart0 SEQUENCE {
      tx ENUMERATED { pa10 },
      rx ENUMERATED { pa9 }
   },
   uart1 SEQUENCE {
      tx ENUMERATED { pa4, pa6, pd26 },
      rx ENUMERATED { pa5 }
   },
   uart2 SEQUENCE {
      tx ENUMERATED { pd26 },
      rx ENUMERATED { pd25 }
   },
   uart3 SEQUENCE {
      tx ENUMERATED { pd30, pd31 },
      rx ENUMERATED { pd28 }
   },
   uart4 SEQUENCE {
      tx ENUMERATED { pd3, pd19 },
      rx ENUMERATED { pd18 }
   }
}

Serial-SamV71-Rtems-Baudrate-T  ::= ENUMERATED {b9600, b19200, b38400, b57600, b115200, b230400}

Serial-SamV71-Rtems-Parity-T    ::= ENUMERATED {even, odd, none}

Serial-SamV71-Escape-Byte-T ::= INTEGER(0..255)

-- The choice option cannot be NULL or empty SEQUENCE to work with space creator.
Serial-Samv71-Rtems-Dummy ::= BOOLEAN

Serial-SamV71-Rtems-Packetizer-Mode-T    ::= CHOICE {
   escaped-packets BOOLEAN,
   raw CHOICE {
      -- Single-byte mode: driver passes the received bytes immediately after reception.
      single-byte         Serial-Samv71-Rtems-Dummy,
      -- Custom escape mode: Driver passes all the received bytes to user application
      --                     after receiving specified byte.
      custom-escape-byte  Serial-SamV71-Escape-Byte-T
   }
}

-- Transmission handling mode
Serial-SamV71-Rtems-Tx-Mode-T ::= ENUMERATED {
   -- Uses DMA, recommended for escaped-packets and large amount of data
   asynchronous,
   -- Synchronously writes bytes, recommended for single-byte mode and small amounts of data
   blocking
}

Serial-SamV71-Rtems-Conf-T ::= SEQUENCE {
   devname          Serial-SamV71-Rtems-Device-T,
   speed            Serial-SamV71-Rtems-Baudrate-T,
   parity           Serial-SamV71-Rtems-Parity-T,
   packetizer-mode  Serial-SamV71-Rtems-Packetizer-Mode-T,
   tx-mode          Serial-SamV71-Rtems-Tx-Mode-T
}

END
