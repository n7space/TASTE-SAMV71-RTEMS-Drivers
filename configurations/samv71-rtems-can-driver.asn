SAMV71-RTEMS-CAN-DRIVER DEFINITIONS AUTOMATIC TAGS ::= BEGIN

    CAN-Samv71-Rtems-Interface-T ::= CHOICE {
        mcan0 SEQUENCE {
            tx ENUMERATED { pb2 },
            rx ENUMERATED { pb3 }
        },
        mcan1 SEQUENCE {
            tx ENUMERATED { pc14, pd12 },
            rx ENUMERATED { pc12 }
        }
    }

    CAN-Samv71-Rtems-PCK-Clock-Source ::= ENUMERATED {
        pck-clock-source-main-clock,
        pck-clock-source-plla-clock
    }

    CAN-Samv71-Rtems-PCK-Prescaler ::= INTEGER (0 .. 255)

    CAN-Samv71-Rtems-Data-Synchronization-Jump-Width ::= INTEGER (0 .. 7)

    CAN-Samv71-Rtems-Data-Time-Segment-Before-Sample-Point ::= INTEGER (1 .. 31)

    CAN-Samv71-Rtems-Data-Time-Segment-After-Sample-Point ::= INTEGER (0 .. 15)

    CAN-Samv71-Rtems-Data-Bit-Rate-Prescaler ::= INTEGER (0 .. 31)

    CAN-Samv71-Rtems-Standard-Can-Id ::= INTEGER (0 .. 2047)

    CAN-Samv71-Rtems-Extended-Can-Id ::= INTEGER (0 .. 536870911)

    CAN-Samv71-Rtems-Can-Id ::= CHOICE {
        can-id-standard CAN-Samv71-Rtems-Standard-Can-Id,
        can-id-extended CAN-Samv71-Rtems-Extended-Can-Id
    }

    -- The choice option cannot be NULL or empty SEQUENCE to work with space creator.
    CAN-Samv71-Rtems-Dummy ::= BOOLEAN

    -- This determines what value shall be used for CAN-ID for output frames.
    CAN-Samv71-Rtems-Address ::= CHOICE {
        -- The first option sets one constant CAN-ID for all output frames.
        static-can-id CAN-Samv71-Rtems-Can-Id,
        -- The second option allows the application to specify exact value of CAN-ID.  Driver uses first four
        -- bytes of every message interpreted as uint32_t to determine CAN-ID. The lowest 11 or 29 bits are a
        -- value of CAN-ID, where bit 30 determines if CAN-ID is standard (11 bit) or extended (29 bit).  The
        -- actual data to send in a frame begins from byte 5 of message.
        application-control-can-id CAN-Samv71-Rtems-Dummy
    }

    CAN-Samv71-Rtems-Conf-T ::= SEQUENCE {
        can-interface CAN-Samv71-Rtems-Interface-T,
        bit-rate-prescaler CAN-Samv71-Rtems-Data-Bit-Rate-Prescaler DEFAULT 0,
        synchronization-jump CAN-Samv71-Rtems-Data-Synchronization-Jump-Width DEFAULT 2,
        time-segments-after-sample-point CAN-Samv71-Rtems-Data-Time-Segment-After-Sample-Point DEFAULT 2,
        time-segments-before-sample-point CAN-Samv71-Rtems-Data-Time-Segment-Before-Sample-Point DEFAULT 15,

        pck-source CAN-Samv71-Rtems-PCK-Clock-Source DEFAULT pck-clock-source-plla-clock,
        pck-prescaler CAN-Samv71-Rtems-PCK-Prescaler DEFAULT 14,
        address CAN-Samv71-Rtems-Address
    }

END
